import FreeCAD
from pivy import coin
from copy import copy
clip=coin.SoClipPlane()

ImageSizeX_iso = 2000 # 919
ImageSizeY_iso = 1000 # 598
ImageSizeX_side = 2000 # 919
ImageSizeY_side = 1250 # 598
ImageSizeX_end = 2000 # 919
ImageSizeY_end = 2000 # 598

def save_image(image_suffix, imageSizeX, imageSizeY):
    doc_name = Gui.ActiveDocument.Document.Label
    root_path = FreeCAD.ActiveDocument.FileName
    out_path, _1 = os.path.split(root_path)
    out_loc = ''.join((out_path ,'/', doc_name, '_', image_suffix))
    Gui.activeDocument().activeView().saveImage(''.join((out_loc, '.png')), imageSizeX, imageSizeY, 'Current')
    clip.plane.setValue(coin.SbPlane(coin.SbVec3f(-1,0,0),0)) #  set this to control the clipping plane
    Gui.ActiveDocument.ActiveView.getSceneGraph().insertChild(clip,0)
    clip.on.setValue(True) # switch on
    Gui.activeDocument().activeView().saveImage(''.join((out_loc, '_yz_cut',  '.png')), imageSizeX, imageSizeY, 'Current')
    clip.on.setValue(False) # switch off
    clip.plane.setValue(coin.SbPlane(coin.SbVec3f(0,1,0),0)) #  set this to control the clipping plane
    Gui.ActiveDocument.ActiveView.getSceneGraph().insertChild(clip,0)
    clip.on.setValue(True) # switch on
    Gui.activeDocument().activeView().saveImage(''.join((out_loc, '_xz_cut',  '.png')), imageSizeX, imageSizeY, 'Current')
    clip.on.setValue(False) # switch off
    clip.plane.setValue(coin.SbPlane(coin.SbVec3f(0,0,-1),0)) #  set this to control the clipping plane
    Gui.ActiveDocument.ActiveView.getSceneGraph().insertChild(clip,0)
    clip.on.setValue(True) # switch on
    Gui.activeDocument().activeView().saveImage(''.join((out_loc, '_xy_cut',  '.png')), imageSizeX, imageSizeY, 'Current')
    clip.on.setValue(False) # switch off

Gui.activeDocument().activeView().viewIsometric()
Gui.SendMsgToActiveView("ViewFit")
save_image('iso',  ImageSizeX_iso, ImageSizeY_iso)

Gui.activeDocument().activeView().viewRight()
Gui.SendMsgToActiveView("ViewFit")
save_image('yz',  ImageSizeX_iso, ImageSizeY_end)

Gui.activeDocument().activeView().viewLeft()
Gui.SendMsgToActiveView("ViewFit")
save_image('-yz',  ImageSizeX_iso, ImageSizeY_end)

Gui.activeDocument().activeView().viewTop()
Gui.SendMsgToActiveView("ViewFit")
save_image('-xy', ImageSizeX_side, ImageSizeY_side)

Gui.activeDocument().activeView().viewBottom()
Gui.SendMsgToActiveView("ViewFit")
save_image('xy', ImageSizeX_side, ImageSizeY_side)

Gui.activeDocument().activeView().viewFront()
Gui.SendMsgToActiveView("ViewFit")
save_image('xz', ImageSizeX_side, ImageSizeY_side)

Gui.activeDocument().activeView().viewRear()
Gui.SendMsgToActiveView("ViewFit")
save_image('-xz', ImageSizeX_side, ImageSizeY_side)

objs = FreeCAD.ActiveDocument.Objects
old_vis = []
for obj in objs:
    old_vis.append(obj.ViewObject.Visibility)
    obj.ViewObject.Visibility=False
    if "_vac" in obj.Label:
         obj.ViewObject.Visibility=True

Gui.activeDocument().activeView().viewIsometric()
Gui.SendMsgToActiveView("ViewFit")
save_image('vac', ImageSizeX_iso, ImageSizeY_iso)

ck = 0
for obj in objs:
    obj.ViewObject.Visibility=old_vis[ck]
    ck = ck + 1

clip.on.setValue(False) # switch off
