import FreeCAD
from pivy import coin
from copy import copy
import Mesh
import MeshPart
import os
import inspect

doc_name = Gui.ActiveDocument.Document.Label
out_name = doc_name.replace('_Base', '')
root_path = FreeCAD.ActiveDocument.FileName
out_path, _1 = os.path.split(root_path)
if not os.path.exists(os.path.join(out_path,'ascii')):
    os.mkdir(os.path.join(out_path,'ascii'))

objs = FreeCAD.ActiveDocument.Objects
for obj in objs:
    temp_properties = obj.PropertiesList
    if "Mesh" in temp_properties:
        try:
            modelPart=FreeCAD.ActiveDocument.getObject(obj.Name)  
            if "(Meshed)" in obj.Label:  
                meshName = obj.Label.replace(' (Meshed)', '')
            else:
                meshName = obj.Label        
            modelPart.Mesh.write(os.path.join(out_path, 'ascii', ''.join([out_name,'-',meshName, '.stl'])), "AST", obj.Label)    
        except:
            print('Error exporting STL for ', obj.Label)
