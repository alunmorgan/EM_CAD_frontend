import FreeCAD
from pivy import coin
from copy import copy
import Mesh
import MeshPart
import os
clip=coin.SoClipPlane()

mesh_resolution=5
doc_name = Gui.ActiveDocument.Document.Label
parts = []
for obj in FreeCAD.ActiveDocument.Objects:
    parts.append(obj.Label)

objs = FreeCAD.ActiveDocument.Objects
for obj in objs:
    a = obj.Name
    b = obj.Label
    c = obj.InList
    if c != []: # Only process top level objects
        continue
    if b == "X_Axis" or   b == "Y_Axis"  or b == "Z_Axis" or  b == "XY_Plane" or  b == "XZ_Plane" or  b == "YZ_Plane" or  b == "Origin" or b == "component1|vessel":
        continue
    if "(Meshed)" in b:
        continue
    print(b)
    __part__=FreeCAD.ActiveDocument.getObject(a)    
    __shape__=__part__.Shape.copy(False)
    mymesh =FreeCAD.ActiveDocument.addObject("Mesh::Feature","Mesh")
    mymesh.Mesh = MeshPart.meshFromShape(Shape=__shape__, LinearDeflection=0.2, AngularDeflection=0.0174533,  Relative=True)
    mymesh.Label = b + " (Meshed)"
    del   __part__, __shape__
